Attribute VB_Name = "ErrorMsgMicrosoft"
Option Explicit

Sub CATMain()

Dim Msg
' If an error occurs, construct an error message
On Error Resume Next    ' Defer error handling.
Err.Clear
Err.Raise 6    ' Generate an "Overflow" error.
' Check for error, then show message.
If Err.Number <> 0 Then
    Msg = "Error # " & Str(Err.Number) & " was generated by " _
            & Err.Source & Chr(13) & Err.Description
    MsgBox Msg, , "Error", Err.HelpFile, Err.HelpContext
End If

End Sub

Attribute VB_Name = "FeatureSet"
Option Explicit

Sub CATMain()

'Creates a pre-configured geometrical set

        Dim partDocument1 As Document
        Dim part1 As Part
        Dim hybridShapefactory1 As HybridShapeFactory
        Dim prefix As String
        Dim bodies1, Bodies2, Bodies3, Bodies4, Bodies31, Bodies32 As HybridBodies
        Dim body1, body2, body3, body31, body32, body4 As HybridBody

        Set partDocument1 = CATIA.ActiveDocument
        Set part1 = partDocument1.Part
        Set hybridShapefactory1 = part1.HybridShapeFactory
        
        prefix = InputBox("Feature Name:", "RA cmd: Feature Set") 'Asks for the prefix for geosets below. Example "bracket.feature"
        
        Set bodies1 = part1.HybridBodies
        Set body1 = bodies1.Add()
        body1.name = prefix + ".Feature" 'Creates the top node called ".feature"

        Set Bodies2 = body1.HybridBodies
        Set body2 = Bodies2.Add()
        body2.name = prefix + ".Input" 'Creates branch called ".input"

        Set Bodies3 = body1.HybridBodies
        Set body3 = Bodies3.Add()
        body3.name = prefix + ".Working" 'Creates branch called ".input"

        Set Bodies31 = body3.HybridBodies
        Set body31 = Bodies31.Add()
        body31.name = prefix + ".Working.Parents" 'Creates a sub-branch in ".working"

        Set Bodies32 = body3.HybridBodies
        Set body32 = Bodies32.Add()
        body32.name = prefix + ".Working.Children" 'Creates another sub-branch in ".working"

        Set Bodies4 = body1.HybridBodies
        Set body4 = Bodies4.Add()
        body4.name = prefix + ".Output" 'Creates branch called ".Output"

        part1.Update

End Sub

Attribute VB_Name = "ParentSelectionList"
Option Explicit

Sub CATMain()

    Dim partDocument1, part1, Selection1

        Set partDocument1 = CATIA.ActiveDocument
        Set part1 = partDocument1.Part
        Set Selection1 = partDocument1.Selection 'Gets the objectcollection in selection

        Dim NumberOfElements As Integer
        NumberOfElements = Selection1.Count

            If NumberOfElements = 0 Then
            MsgBox "Nothing is selected", , "RA_SelectionList"
            Exit Sub
            End If 'Error handling if nothing is selected

        Dim StopValue As String
        Dim SelectedElement1 As SelectedElement
        Dim i As Integer
        Dim MessageList As String
        Dim Item As AnyObject
        
        i = 1
        
        Do Until i = NumberOfElements
            
            SelectedElement1 = Selection1.Item(i)
            Item = SelectedElement1.Value
                Do Until StopValue = "CNEXT"
                    MessageList = MessageList & Item.name & " " & Item.Parent & Chr(13)
                    StopValue = Item.name
                    Item = Item.Parent
                Loop
            StopValue = ""
            i = i + 1
        Loop
        
        MsgBox (MessageList)
        
        



'        For i = 1 To NumberOfElements
'            SelectionList = SelectionList & "TYPE: " & Selection1.Item(i).Type & " NAME: " & Selection1.Item(i).Value.Name & Chr(13)
'        Next
        
        'MsgBox (SelectionList)

End Sub

Attribute VB_Name = "RA_ConvertVertex"
Option Explicit

Sub CATMain()

Dim partDocument1 As Document
Set partDocument1 = CATIA.ActiveDocument
Dim part1 As Part
Set part1 = partDocument1.Part
Dim hybridBodies1 As HybridBodies
Set hybridBodies1 = part1.HybridBodies
Dim hybridShapefactory1 As HybridShapeFactory
Set hybridShapefactory1 = part1.HybridShapeFactory
        
        Dim HybridBody1 As HybridBody
        If TypeName(part1.InWorkObject) = "HybridBody" Then
            Set HybridBody1 = part1.InWorkObject 'Uses the GeoSet in work object
        Else
            Set HybridBody1 = hybridBodies1.Item(hybridBodies1.Count) 'If no geoset in work object last geoset is used
        End If


        Dim InputObjectType(1), Status, Selection1
        Set Selection1 = partDocument1.Selection
            InputObjectType(0) = "Vertex"
            InputObjectType(1) = "Point"
            Status = Selection1.SelectElement2(InputObjectType, "RA_ConvertVertex Command: Select Point or Vertex", True) 'asks the user to select point or vertex
        If (Status = "Cancel") Then
            Exit Sub
        End If
            
        Dim Reference1 As Reference
        Set Reference1 = Selection1.Item(1).Reference 'Creates Reference from point or vertex
            Selection1.Clear

        Dim hybridShapePointCoord1 'As HybridShapePointCoord
        Set hybridShapePointCoord1 = hybridShapefactory1.AddNewPointCoordWithReference(0, 0, 0, Reference1) 'Creates Point on vertex
            HybridBody1.AppendHybridShape hybridShapePointCoord1 'Adds point to GeoSet
            part1.InWorkObject = hybridShapePointCoord1: part1.Update

        Dim Coordinates1(2), hybridShapePointCoord2
            hybridShapePointCoord1.GetCoordinates Coordinates1
        Set hybridShapePointCoord2 = hybridShapefactory1.AddNewPointCoord(Coordinates1(0), Coordinates1(1), Coordinates1(2))
            HybridBody1.AppendHybridShape hybridShapePointCoord2 'Adds point to GeoSet
            Selection1.Clear
            Selection1.Add hybridShapePointCoord1
            Selection1.Delete
            Selection1.Clear
            part1.InWorkObject = hybridShapePointCoord2: part1.Update

End Sub

Attribute VB_Name = "RA_CustomSet"
Option Explicit
Const ForReading = 1

'This Script creates mini tree of geosets predefined in a .txt file on a user picked location
'The Sytax for the .txt is:
'Parent,child
'Parent,Child
'Parent,Child
'Be careful not to misspell

Sub CATMain()
                           
'Error handling
Dim Msg
On Error Resume Next
Err.Clear

Dim FileSystemObject1 As Object
Set FileSystemObject1 = CreateObject("Scripting.FileSystemObject")

Dim SourceFile As Object
Dim myFilePath As String
Dim SourceFileText As String

myFilePath = "C:\Users\Anv\Dropbox\Projekt\kod\CatiaMacros\SourceFiles\FeatureSet.txt" 'Specify User Local .txt filepath

Set SourceFile = FileSystemObject1.OpenTextFile(myFilePath, ForReading)
SourceFileText = SourceFile.ReadAll
SourceFile.Close 'gets the text to the variable

Dim N As Variant
Dim iNodes As Integer
Dim NodeArray() As String
NodeArray = Split(SourceFileText, Chr(13))
iNodes = -1

For Each N In NodeArray
iNodes = iNodes + 1
Next N 'Gets Index of Nodes including top node

Dim i As Integer
ReDim ChildName(iNodes) As String 'Creates an array with the length of the childnodes
ReDim ParentName(iNodes) As String 'Creates an array with the length of the parentnodes
Dim ParentChildArray() As String

For i = 0 To iNodes
ParentChildArray = Split(NodeArray(i), ",")
ChildName(i) = ParentChildArray(1)
ParentName(i) = ParentChildArray(0)
Next 'Fills The Arrays with Child and Parent names

    Dim partDocument1 As Document
    Dim part1 As Part
    Dim Selection1 As Selection
        
        Set partDocument1 = CATIA.ActiveDocument
        Set Selection1 = partDocument1.Selection: Selection1.Clear
        Set part1 = partDocument1.Part
        
    Dim hybridBodies1 As HybridBodies
    Dim HybridBody1 As HybridBody
        
    Dim prefix As String
        prefix = ""
        prefix = InputBox("Write a prefix for your custom geoset", "RA_CustomGeoSet")
    
    Dim TargetName As String
    TargetName = ""
    If TypeName(part1.InWorkObject) = "HybridBody" Then
    TargetName = part1.InWorkObject.name
    End If
    
        For i = 0 To iNodes
        Set hybridBodies1 = part1.HybridBodies
        Set HybridBody1 = hybridBodies1.Add()
        HybridBody1.name = prefix & ChildName(i) 'Creates all the nodes inside the part
        Next
        part1.Update
        
    For i = 1 To iNodes
        Selection1.Search ("Name=" & prefix & ChildName(i) & ",all")
        Selection1.Cut: Selection1.Clear
        Selection1.Search ("Name=" & prefix & ParentName(i) & ",all")
        Selection1.Paste: Selection1.Clear
    Next
        
        If TargetName <> "" Then
        Selection1.Search ("Name=" & prefix & ChildName(0) & ",all")
        Selection1.Cut: Selection1.Clear
        Selection1.Search ("Name=" & TargetName & ",all")
        Selection1.Paste: Selection1.Clear
        Else
        Selection1.Search ("Name=" & prefix & ChildName(0) & ",all")
        part1.InWorkObject = Selection1.Item(1).Value
        Selection1.Clear
        End If                      'Puts the sets in the geoset in work object
        
        part1.Update
               

                    If Err.Number <> 0 Then
                    Msg = "Error # " & Str(Err.Number) & " was generated by " & Err.Source & Chr(13) & Err.Description
                    MsgBox Msg, , "Error", Err.HelpFile, Err.HelpContext
                    End If

End Sub

Attribute VB_Name = "RA_IsolatedCube"
Option Explicit

Sub CATMain()

            Dim partDocument1 As Document
            Dim part1 As Part
            Dim hybridBodies1 As HybridBodies
            Dim hybridShapefactory1 As HybridShapeFactory
            Dim Selection1 As Selection
            Dim Dimension1 As Double: Dimension1 = InputBox("Enter Cube dimensions") 'gets cube dimensions from user
                        
            Set partDocument1 = CATIA.ActiveDocument
            Set part1 = partDocument1.Part
            Set hybridShapefactory1 = part1.HybridShapeFactory
            Set hybridBodies1 = part1.HybridBodies
            Set Selection1 = partDocument1.Selection: Selection1.Clear
            
            Dim HybridBody1 As HybridBody
            Set HybridBody1 = hybridBodies1.Add: part1.Update 'Creates a dummy geoset
            
            Dim ClickSelection As Object
            Set ClickSelection = Selection1
            
            Dim InputObjectType(1), Status
                InputObjectType(0) = "Vertex"
                InputObjectType(1) = "Point"
                Status = ClickSelection.SelectElement2(InputObjectType, "RA_IsolatedCube Command: Select point or vertex for cube origin", True)
        
        If Status = "Cancel" Then
                Exit Sub
        End If
            Dim Reference1 As Reference
            Set Reference1 = Selection1.Item(1).Reference: Selection1.Clear 'creates reference vertex/point
            
            Dim Point1 As HybridShapePointCoord
            Set Point1 = hybridShapefactory1.AddNewPointCoordWithReference(0, 0, 0, Reference1)
                HybridBody1.AppendHybridShape Point1: part1.Update 'creates point
                                  
            Dim Point2 As HybridShapePointCoord
            Set Point2 = hybridShapefactory1.AddNewPointCoordWithReference(0, 0, Dimension1, Point1)
                HybridBody1.AppendHybridShape Point2: part1.Update 'creates point
                
            Dim Point3 As HybridShapePointCoord
            Set Point3 = hybridShapefactory1.AddNewPointCoordWithReference(0, Dimension1, 0, Point1)
                HybridBody1.AppendHybridShape Point3: part1.Update 'creates point
            
            Dim Line1 As HybridShapeLinePtPt
            Set Line1 = hybridShapefactory1.AddNewLinePtPt(Point1, Point2)
                HybridBody1.AppendHybridShape Line1: part1.Update 'creates line
            
            Dim Line2 As HybridShapeLinePtPt
            Set Line2 = hybridShapefactory1.AddNewLinePtPt(Point1, Point3)
                HybridBody1.AppendHybridShape Line2: part1.Update 'creates line
            
            Dim hybridShapeDirection1 As HybridShapeDirection
            Set hybridShapeDirection1 = hybridShapefactory1.AddNewDirection(Line2)
            
            Dim hybridShapeExtrude1 As HybridShapeExtrude
            Set hybridShapeExtrude1 = hybridShapefactory1.AddNewExtrude(Line1, Dimension1, 0#, hybridShapeDirection1)
                HybridBody1.AppendHybridShape hybridShapeExtrude1: part1.Update
            
            Dim bodies1 As Bodies
            Set bodies1 = part1.Bodies
            Dim ShapeFactory1 As ShapeFactory
            Set ShapeFactory1 = part1.ShapeFactory
            Dim body1 As Body
            Set body1 = bodies1.Add: body1.name = "Cube": part1.Update 'creates a new body
            
            Dim Reference2 As Reference
            Set Reference2 = part1.CreateReferenceFromName("")
            Dim Thicksurface1 As ThickSurface
            Set Thicksurface1 = ShapeFactory1.AddNewThickSurface(Reference2, 0, 1#, 0#)
                Thicksurface1.Surface = hybridShapeExtrude1
            Dim Length1 As Length
            Set Length1 = Thicksurface1.TopOffset
                Length1.Value = Dimension1
            Dim Length2 As Length
            Set Length2 = Thicksurface1.BotOffset
                Length2.Value = 0
                part1.InWorkObject = body1: part1.Update 'Creates a thicksurface in the new body
            
            Selection1.Add body1
            Selection1.Copy
            Selection1.PasteSpecial ("CATPrtResultWithOutLink")
            Selection1.Clear
            part1.Update
            
            Selection1.Add body1
            Selection1.Add HybridBody1
            Selection1.Delete
            Selection1.Clear
            part1.Update
            
            bodies1.Item(bodies1.Count).Shapes.Item(1).name = "Cube"
            
            part1.Update
        
            
End Sub

Attribute VB_Name = "RA_OriginSurface"
Sub CATMain()

Dim partDocument1 As PartDocument
Set partDocument1 = CATIA.ActiveDocument
Dim part1 As Part
Set part1 = partDocument1.Part
Dim hybridShapefactory1 As HybridShapeFactory
Set hybridShapefactory1 = part1.HybridShapeFactory

Dim Selection1, Status, InputObject(0)
Set Selection1 = partDocument1.Selection
InputObject(0) = "Edge"
Status = Selection1.SelectElement2(InputObject, "Select surface edge", True)
If Status = "CANCEL" Then Exit Sub

Dim EdgeReference1 As Reference
Set EdgeReference1 = Selection1.Item(1).Reference: Selection1.Clear

InputObject(0) = "Face"
Status = Selection1.SelectElement2(InputObject, "Select surface face", True)
If Status = "CANCEL" Then
Exit Sub
End If

Dim FaceReference1 As Reference
Set FaceReference1 = Selection1.Item(1).Reference: Selection1.Clear

Dim hybridShapeExtrapol1 As HybridShapeExtrapol
Set hybridShapeExtrapol1 = hybridShapefactory1.AddNewExtrapolLength(EdgeReference1, FaceReference1, 100#)

hybridShapeExtrapol1.BorderType = 1
hybridShapeExtrapol1.SetAssemble True
hybridShapeExtrapol1.PropagationMode = 2
hybridShapeExtrapol1.ExtendEdgesMode = False
hybridShapeExtrapol1.ConstantLengthMode = False
hybridShapeExtrapol1.SetContinuityType 1, 1

Dim HybridBody1 As HybridBody

If TypeName(part1.InWorkObject) = "HybridBody" Then
            Set HybridBody1 = part1.InWorkObject
        Else
            Set HybridBody1 = hybridBodies1.Item(hybridBodies1.Count)
        End If

        HybridBody1.AppendHybridShape hybridShapeExtrapol1
        part1.Update: part1.InWorkObject = hybridShapeExtrapol1: Selection1.Clear

End Sub

Attribute VB_Name = "RA_PowerRename"
Option Explicit

Sub CATMain()

    Dim Msg 'If an error occurs, construct an error message
        On Error Resume Next 'Defer error handling.
        Err.Clear

    Dim partDocument1, part1, Selection1
    
        Set partDocument1 = CATIA.ActiveDocument
        Set part1 = partDocument1.Part
        Set Selection1 = partDocument1.Selection 'Gets the objectcollection in selection
    
            If Selection1.Count = 0 Then
            MsgBox "Nothing is selected", , "RA_PowerRename"
            Exit Sub
            End If 'Error handling if nothing is selected
    
    Dim NumberOfElements As Integer
    Dim InputString As String
    Dim OutputString As String
    Dim TestArray() As String
    Dim T As Variant
    Dim iTestArray As Integer
    Dim i As Integer
    
            NumberOfElements = Selection1.Count
            InputString = InputBox("New name, new prefix- or new -suffix", "RA_PowerRename") 'Asks user for new name
            TestArray = Split(InputString, "-")
            iTestArray = -1
        
        If NumberOfElements = 1 Then
        Selection1.Item(1).Value.name = InputString
        Exit Sub
        End If 'For one element no suffix is needed
        
            For Each T In TestArray
                iTestArray = iTestArray + 1
            Next T 'gets the indexlength of the user input with zero as first number
        
        If TestArray(0) = "" And Not TestArray(iTestArray) = "" Then 'minus first
            For i = 1 To NumberOfElements
                Selection1.Item(i).Value.name = Selection1.Item(i).Value.name & TestArray(1)
            Next
        
        ElseIf TestArray(iTestArray) = "" And Not TestArray(0) = "" Then 'minus last
            For i = 1 To NumberOfElements
                Selection1.Item(i).Value.name = TestArray(0) & Selection1.Item(i).Value.name
            Next
            
        Else
            For i = 1 To NumberOfElements
                Selection1.Item(i).Value.name = TestArray(0) & i
            Next
            
        End If
        
        If Err.Number <> 0 Then
            Msg = "Error # " & Str(Err.Number) & " was generated by " & Err.Source & Chr(13) & Err.Description
            MsgBox Msg, , "Error", Err.HelpFile, Err.HelpContext
        End If

End Sub

Attribute VB_Name = "SearchTesting"
Option Explicit

Sub CATMain()

Dim partDocument1, part1
Dim Selection1 As Selection

Set partDocument1 = CATIA.ActiveDocument
Set part1 = partDocument1.Part
Set Selection1 = partDocument1.Selection: Selection1.Clear
Dim name As String
name = "Point1"
Selection1.Search ("Name=" & name & ",all")
Selection1.Cut: Selection1.Clear
Selection1.Search ("Name=.Input,all")
Selection1.Paste: Selection1.Clear

part1.Update

End Sub

Attribute VB_Name = "SelectionList"
Option Explicit

Sub CATMain()

    Dim partDocument1, part1, Selection1

        Set partDocument1 = CATIA.ActiveDocument
        Set part1 = partDocument1.Part
        Set Selection1 = partDocument1.Selection 'Gets the objectcollection in selection

        Dim NumberOfElements As Integer
        NumberOfElements = Selection1.Count

            If NumberOfElements = 0 Then
            MsgBox "Nothing is selected", , "RA_SelectionList"
            Exit Sub
            End If 'Error handling if nothing is selected

        Dim i
        Dim SelectionList As String

        For i = 1 To NumberOfElements
            SelectionList = SelectionList & "TYPE: " & Selection1.Item(i).Type & " NAME: " & Selection1.Item(i).Value.name & Chr(13)
        Next
        
        MsgBox (SelectionList)

End Sub

Attribute VB_Name = "TextFileWrite"
Option Explicit
Const ForReading = 1
Const ForWriting = 2
Const ForAppending = 8

Sub CATMain()
                            
                                    Dim Msg 'If an error occurs, construct an error message
                                    On Error Resume Next 'Defer error handling.
                                    Err.Clear
        
Dim FileSystemObject1 As Object
Set FileSystemObject1 = CreateObject("Scripting.FileSystemObject")

Dim Textfile1 As Object
Dim myFilePath As String
Dim myFileText As String

myFilePath = "C:\Users\Anv\Dropbox\Projekt\kod\CatiaMacros\TextFiles\HelloWorld.txt"

Set Textfile1 = FileSystemObject1.CreateTextFile(myFilePath, True)
Textfile1.WriteLine ("HelloWorld")
Textfile1.Close

Set Textfile1 = FileSystemObject1.OpenTextFile(myFilePath, ForReading)
myFileText = Textfile1.ReadAll
Textfile1.Close






MsgBox (myFileText)
    
    

                                    If Err.Number <> 0 Then
                                    Msg = "Error # " & Str(Err.Number) & " was generated by " & Err.Source & Chr(13) & Err.Description
                                    MsgBox Msg, , "Error", Err.HelpFile, Err.HelpContext
                                    End If

End Sub

Attribute VB_Name = "TextFiletest"
Option Explicit
Const ForReading = 1
Const ForWriting = 2
Const ForAppending = 8

Sub CATMain()
                            
                                    Dim Msg 'If an error occurs, construct an error message
                                    On Error Resume Next 'Defer error handling.
                                    Err.Clear
        
Dim FileSystemObject1 As Object
Set FileSystemObject1 = CreateObject("Scripting.FileSystemObject")

Dim Readfile1 As Object
Dim myReadFilePath As String
Dim myReadFileText As String

myReadFilePath = "C:\Users\Anv\Dropbox\Projekt\kod\CatiaMacros\TextRead\address.txt"

'Set Textfile1 = FileSystemObject1.CreateTextFile(myFilePath, True)
'Textfile1.WriteLine ("HelloWorld")
'Textfile1.Close

Set Readfile1 = FileSystemObject1.OpenTextFile(myReadFilePath, ForReading)
myReadFileText = Readfile1.ReadAll
Readfile1.Close

Dim WriteFile1 As Object
Dim Message As String
Set WriteFile1 = FileSystemObject1.OpenTextFile(myReadFileText, ForReading)
Message = WriteFile1.ReadAll
WriteFile1.Close



MsgBox (Message)
    
    

                                    If Err.Number <> 0 Then
                                    Msg = "Error # " & Str(Err.Number) & " was generated by " & Err.Source & Chr(13) & Err.Description
                                    MsgBox Msg, , "Error", Err.HelpFile, Err.HelpContext
                                    End If

End Sub
