Attribute VB_Name = "Module1"
Sub CATMain()

Dim NameSplit() As String
NameSplit = Split(CATIA.ActiveDocument.Name, ".")

If NameSplit(1) = "CATProduct" Then
MsgBox ("Product is active")
End If

If NameSplit(1) = "CATPart" Then
MsgBox ("Part is active")
End If

End Sub

Attribute VB_Name = "Module2"
Sub CATMain()

Dim partDocument1 As PartDocument
Set partDocument1 = CATIA.ActiveDocument

Dim selection1 As Selection
Set selection1 = partDocument1.Selection

selection1.Clear

Dim part1 As Part
Set part1 = partDocument1.Part

Dim bodies1 As Bodies
Set bodies1 = part1.Bodies

Dim body1 As Body
Set body1 = bodies1.Item("Player.5")

selection1.Add body1

selection1.Copy

part1.Update

End Sub

Attribute VB_Name = "Module3"
Sub CATMain()

End Sub

Attribute VB_Name = "Module4"
Sub CATMain()

End Sub

Attribute VB_Name = "Module5"
Sub CATMain()

End Sub

Attribute VB_Name = "Move"
Sub CATMain()

Dim partDocument1 As PartDocument
Set partDocument1 = CATIA.ActiveDocument

Dim selection1 As Selection
Set selection1 = partDocument1.Selection

selection1.Clear

Dim part1 As Part
Set part1 = partDocument1.Part

Dim bodies1 As Bodies
Set bodies1 = part1.Bodies

Dim body1 As Body
Set body1 = bodies1.Item("helperCube")

selection1.Add body1

selection1.Copy

part1.Update

part1.Update

part1.Update

End Sub

Attribute VB_Name = "Part_in_macro2"
Sub CATMain()

Dim documents1 As Documents
Set documents1 = CATIA.Documents

Dim partDocument1 As PartDocument
Set partDocument1 = documents1.Item("Part1.CATPart")

Dim part1 As Part
Set part1 = partDocument1.Part

Dim hybridBodies1 As HybridBodies
Set hybridBodies1 = part1.HybridBodies

Dim hybridBody1 As HybridBody
Set hybridBody1 = hybridBodies1.Item("Geometrical Set.1")

Dim sketches1 As Sketches
Set sketches1 = hybridBody1.HybridSketches

Dim reference1 As Reference
Set reference1 = part1.CreateReferenceFromName("Selection_RSur:(Face:(Brp:(AxisSystem.1;1);None:();Cf11:());AxisSystem.1;Z0;G7575)")

Dim sketch1 As Sketch
Set sketch1 = sketches1.Add(reference1)

Dim arrayOfVariantOfDouble1(8)
arrayOfVariantOfDouble1(0) = 0#
arrayOfVariantOfDouble1(1) = 0#
arrayOfVariantOfDouble1(2) = 0#
arrayOfVariantOfDouble1(3) = 1#
arrayOfVariantOfDouble1(4) = 0#
arrayOfVariantOfDouble1(5) = 0#
arrayOfVariantOfDouble1(6) = 0#
arrayOfVariantOfDouble1(7) = 1#
arrayOfVariantOfDouble1(8) = 0#
Set sketch1Variant = sketch1
sketch1Variant.SetAbsoluteAxisData arrayOfVariantOfDouble1

part1.InWorkObject = sketch1

Dim factory2D1 As Factory2D
Set factory2D1 = sketch1.OpenEdition()

Dim geometricElements1 As GeometricElements
Set geometricElements1 = sketch1.GeometricElements

Dim axis2D1 As Axis2D
Set axis2D1 = geometricElements1.Item("AbsoluteAxis")

Dim line2D1 As Line2D
Set line2D1 = axis2D1.GetItem("HDirection")

line2D1.ReportName = 1

Dim line2D2 As Line2D
Set line2D2 = axis2D1.GetItem("VDirection")

line2D2.ReportName = 2

Dim circle2D1 As Circle2D
Set circle2D1 = factory2D1.CreateClosedCircle(0#, 0#, 39.082559)

Dim point2D1 As Point2D
Set point2D1 = axis2D1.GetItem("Origin")

circle2D1.CenterPoint = point2D1

circle2D1.ReportName = 3

sketch1.CloseEdition

part1.InWorkObject = hybridBody1

part1.Update

End Sub

Attribute VB_Name = "Part_in_product"
Sub CATMain()

End Sub

Attribute VB_Name = "RA_ConvertVertex"
Option Explicit

Sub CATMain()

Dim partDocument1 As document
Set partDocument1 = CATIA.ActiveDocument
Dim part1 As Part
Set part1 = partDocument1.Part
Dim hybridBodies1 As HybridBodies
Set hybridBodies1 = part1.HybridBodies
Dim hybridShapeFactory1 As HybridShapeFactory
Set hybridShapeFactory1 = part1.HybridShapeFactory
        
        Dim hybridBody1 As HybridBody
        If TypeName(part1.InWorkObject) = "HybridBody" Then
            Set hybridBody1 = part1.InWorkObject 'Uses the GeoSet in work object
        Else
            Set hybridBody1 = hybridBodies1.Item(hybridBodies1.Count) 'If no geoset in work object last geoset is used
        End If


        Dim InputObjectType(1), Status, selection1
        Set selection1 = partDocument1.Selection
            InputObjectType(0) = "Vertex"
            InputObjectType(1) = "Point"
            Status = selection1.SelectElement2(InputObjectType, "RA_ConvertVertex Command: Select Point or Vertex", True) 'asks the user to select point or vertex
        If (Status = "Cancel") Then
            Exit Sub
        End If
            
        Dim reference1 As Reference
        Set reference1 = selection1.Item(1).Reference 'Creates Reference from point or vertex
            selection1.Clear

        Dim hybridShapePointCoord1 'As HybridShapePointCoord
        Set hybridShapePointCoord1 = hybridShapeFactory1.AddNewPointCoordWithReference(0, 0, 0, reference1) 'Creates Point on vertex
            hybridBody1.AppendHybridShape hybridShapePointCoord1 'Adds point to GeoSet
            part1.InWorkObject = hybridShapePointCoord1: part1.Update

        Dim Coordinates1(2), hybridShapePointCoord2
            hybridShapePointCoord1.GetCoordinates Coordinates1
        Set hybridShapePointCoord2 = hybridShapeFactory1.AddNewPointCoord(Coordinates1(0), Coordinates1(1), Coordinates1(2))
            hybridBody1.AppendHybridShape hybridShapePointCoord2 'Adds point to GeoSet
            selection1.Clear
            selection1.Add hybridShapePointCoord1
            selection1.Delete
            selection1.Clear
            part1.InWorkObject = hybridShapePointCoord2: part1.Update

End Sub

Attribute VB_Name = "RA_CustomSet"
Option Explicit
Const ForReading = 1

'This Script creates mini tree of geosets predefined in a .txt file on a user picked location
'The Sytax for the .txt is:
'Parent,child
'Parent,Child
'Parent,Child
'Be careful not to misspell

Sub CATMain()
                           
'Error handling
Dim Msg
On Error Resume Next
Err.Clear

Dim FileSystemObject1 As Object
Set FileSystemObject1 = CreateObject("Scripting.FileSystemObject")

Dim SourceFile As Object
Dim myFilePath As String
Dim SourceFileText As String

myFilePath = "C:\Users\Anv\Dropbox\Projekt\kod\CatiaMacros\SourceFiles\FeatureSet.txt" 'Specify User Local .txt filepath

Set SourceFile = FileSystemObject1.OpenTextFile(myFilePath, ForReading)
SourceFileText = SourceFile.ReadAll
SourceFile.Close 'gets the text to the variable

Dim N As Variant
Dim iNodes As Integer
Dim NodeArray() As String
NodeArray = Split(SourceFileText, Chr(13))
iNodes = -1

For Each N In NodeArray
iNodes = iNodes + 1
Next N 'Gets Index of Nodes including top node

Dim i As Integer
ReDim ChildName(iNodes) As String 'Creates an array with the length of the childnodes
ReDim ParentName(iNodes) As String 'Creates an array with the length of the parentnodes
Dim ParentChildArray() As String

For i = 0 To iNodes
ParentChildArray = Split(NodeArray(i), ",")
ChildName(i) = ParentChildArray(1)
ParentName(i) = ParentChildArray(0)
Next 'Fills The Arrays with Child and Parent names

    Dim partDocument1 As document
    Dim part1 As Part
    Dim selection1 As Selection
        
        Set partDocument1 = CATIA.ActiveDocument
        Set selection1 = partDocument1.Selection: selection1.Clear
        Set part1 = partDocument1.Part
        
    Dim hybridBodies1 As HybridBodies
    Dim hybridBody1 As HybridBody
        
    Dim prefix As String
        prefix = ""
        prefix = InputBox("Write a prefix for your custom geoset", "RA_CustomGeoSet")
    
    Dim TargetName As String
    TargetName = ""
    If TypeName(part1.InWorkObject) = "HybridBody" Then
    TargetName = part1.InWorkObject.Name
    End If
    
        For i = 0 To iNodes
        Set hybridBodies1 = part1.HybridBodies
        Set hybridBody1 = hybridBodies1.Add()
        hybridBody1.Name = prefix & ChildName(i) 'Creates all the nodes inside the part
        Next
        part1.Update
        
    For i = 1 To iNodes
        selection1.Search ("Name=" & prefix & ChildName(i) & ",all")
        selection1.Cut: selection1.Clear
        selection1.Search ("Name=" & prefix & ParentName(i) & ",all")
        selection1.Paste: selection1.Clear
    Next
        
        If TargetName <> "" Then
        selection1.Search ("Name=" & prefix & ChildName(0) & ",all")
        selection1.Cut: selection1.Clear
        selection1.Search ("Name=" & TargetName & ",all")
        selection1.Paste: selection1.Clear
        Else
        selection1.Search ("Name=" & prefix & ChildName(0) & ",all")
        part1.InWorkObject = selection1.Item(1).Value
        selection1.Clear
        End If                      'Puts the sets in the geoset in work object
        
        part1.Update
               

                    If Err.Number <> 0 Then
                    Msg = "Error # " & Str(Err.Number) & " was generated by " & Err.Source & Chr(13) & Err.Description
                    MsgBox Msg, , "Error", Err.HelpFile, Err.HelpContext
                    End If

End Sub

Attribute VB_Name = "RA_IsolatedCube"
Option Explicit

Sub CATMain()

            Dim partDocument1 As document
            Dim part1 As Part
            Dim hybridBodies1 As HybridBodies
            Dim hybridShapeFactory1 As HybridShapeFactory
            Dim selection1 As Selection
            Dim Dimension1 As Double: Dimension1 = InputBox("Enter Cube dimensions") 'gets cube dimensions from user
                        
            Set partDocument1 = CATIA.ActiveDocument
            Set part1 = partDocument1.Part
            Set hybridShapeFactory1 = part1.HybridShapeFactory
            Set hybridBodies1 = part1.HybridBodies
            Set selection1 = partDocument1.Selection: selection1.Clear
            
            Dim hybridBody1 As HybridBody
            Set hybridBody1 = hybridBodies1.Add: part1.Update 'Creates a dummy geoset
            
            Dim ClickSelection As Object
            Set ClickSelection = selection1
            
            Dim InputObjectType(1), Status
                InputObjectType(0) = "Vertex"
                InputObjectType(1) = "Point"
                Status = ClickSelection.SelectElement2(InputObjectType, "RA_IsolatedCube Command: Select point or vertex for cube origin", True)
        
        If Status = "Cancel" Then
                Exit Sub
        End If
            Dim reference1 As Reference
            Set reference1 = selection1.Item(1).Reference: selection1.Clear 'creates reference vertex/point
            
            Dim Point1 As HybridShapePointCoord
            Set Point1 = hybridShapeFactory1.AddNewPointCoordWithReference(0, 0, 0, reference1)
                hybridBody1.AppendHybridShape Point1: part1.Update 'creates point
                                  
            Dim Point2 As HybridShapePointCoord
            Set Point2 = hybridShapeFactory1.AddNewPointCoordWithReference(0, 0, Dimension1, Point1)
                hybridBody1.AppendHybridShape Point2: part1.Update 'creates point
                
            Dim Point3 As HybridShapePointCoord
            Set Point3 = hybridShapeFactory1.AddNewPointCoordWithReference(0, Dimension1, 0, Point1)
                hybridBody1.AppendHybridShape Point3: part1.Update 'creates point
            
            Dim Line1 As HybridShapeLinePtPt
            Set Line1 = hybridShapeFactory1.AddNewLinePtPt(Point1, Point2)
                hybridBody1.AppendHybridShape Line1: part1.Update 'creates line
            
            Dim Line2 As HybridShapeLinePtPt
            Set Line2 = hybridShapeFactory1.AddNewLinePtPt(Point1, Point3)
                hybridBody1.AppendHybridShape Line2: part1.Update 'creates line
            
            Dim hybridShapeDirection1 As HybridShapeDirection
            Set hybridShapeDirection1 = hybridShapeFactory1.AddNewDirection(Line2)
            
            Dim hybridShapeExtrude1 As HybridShapeExtrude
            Set hybridShapeExtrude1 = hybridShapeFactory1.AddNewExtrude(Line1, Dimension1, 0#, hybridShapeDirection1)
                hybridBody1.AppendHybridShape hybridShapeExtrude1: part1.Update
            
            Dim bodies1 As Bodies
            Set bodies1 = part1.Bodies
            Dim ShapeFactory1 As ShapeFactory
            Set ShapeFactory1 = part1.ShapeFactory
            Dim body1 As Body
            Set body1 = bodies1.Add: body1.Name = "Cube": part1.Update 'creates a new body
            
            Dim reference2 As Reference
            Set reference2 = part1.CreateReferenceFromName("")
            Dim Thicksurface1 As ThickSurface
            Set Thicksurface1 = ShapeFactory1.AddNewThickSurface(reference2, 0, 1#, 0#)
                Thicksurface1.Surface = hybridShapeExtrude1
            Dim Length1 As Length
            Set Length1 = Thicksurface1.TopOffset
                Length1.Value = Dimension1
            Dim Length2 As Length
            Set Length2 = Thicksurface1.BotOffset
                Length2.Value = 0
                part1.InWorkObject = body1: part1.Update 'Creates a thicksurface in the new body
            
            selection1.Add body1
            selection1.Copy
            selection1.PasteSpecial ("CATPrtResultWithOutLink")
            selection1.Clear
            part1.Update
            
            selection1.Add body1
            selection1.Add hybridBody1
            selection1.Delete
            selection1.Clear
            part1.Update
            
            bodies1.Item(bodies1.Count).Shapes.Item(1).Name = "Cube"
            
            part1.Update
        
            
End Sub

Attribute VB_Name = "RA_OriginSurface"
Sub CATMain()

Dim partDocument1 As PartDocument
Set partDocument1 = CATIA.ActiveDocument
Dim part1 As Part
Set part1 = partDocument1.Part
Dim hybridShapeFactory1 As HybridShapeFactory
Set hybridShapeFactory1 = part1.HybridShapeFactory

Dim selection1, Status, InputObject(0)
Set selection1 = partDocument1.Selection
InputObject(0) = "Edge"
Status = selection1.SelectElement2(InputObject, "Select surface edge", True)
If Status = "CANCEL" Then Exit Sub

Dim EdgeReference1 As Reference
Set EdgeReference1 = selection1.Item(1).Reference: selection1.Clear

InputObject(0) = "Face"
Status = selection1.SelectElement2(InputObject, "Select surface face", True)
If Status = "CANCEL" Then
Exit Sub
End If

Dim FaceReference1 As Reference
Set FaceReference1 = selection1.Item(1).Reference: selection1.Clear

Dim hybridShapeExtrapol1 As HybridShapeExtrapol
Set hybridShapeExtrapol1 = hybridShapeFactory1.AddNewExtrapolLength(EdgeReference1, FaceReference1, 100#)

hybridShapeExtrapol1.BorderType = 1
hybridShapeExtrapol1.SetAssemble True
hybridShapeExtrapol1.PropagationMode = 2
hybridShapeExtrapol1.ExtendEdgesMode = False
hybridShapeExtrapol1.ConstantLengthMode = False
hybridShapeExtrapol1.SetContinuityType 1, 1

Dim hybridBody1 As HybridBody

If TypeName(part1.InWorkObject) = "HybridBody" Then
            Set hybridBody1 = part1.InWorkObject
        Else
            Set hybridBody1 = hybridBodies1.Item(hybridBodies1.Count)
        End If

        hybridBody1.AppendHybridShape hybridShapeExtrapol1
        part1.Update: part1.InWorkObject = hybridShapeExtrapol1: selection1.Clear

End Sub

Attribute VB_Name = "RA_PowerRename"
Option Explicit

Sub CATMain()

    Dim Msg 'If an error occurs, construct an error message
        On Error Resume Next 'Defer error handling.
        Err.Clear

    Dim partDocument1, part1, selection1
    
        Set partDocument1 = CATIA.ActiveDocument
        Set part1 = partDocument1.Part
        Set selection1 = partDocument1.Selection 'Gets the objectcollection in selection
    
            If selection1.Count = 0 Then
            MsgBox "Nothing is selected", , "RA_PowerRename"
            Exit Sub
            End If 'Error handling if nothing is selected
    
    Dim NumberOfElements As Integer
    Dim InputString As String
    Dim OutputString As String
    Dim TestArray() As String
    Dim T As Variant
    Dim iTestArray As Integer
    Dim i As Integer
    
            NumberOfElements = selection1.Count
            InputString = InputBox("New name, new prefix- or new -suffix", "RA_PowerRename") 'Asks user for new name
            TestArray = Split(InputString, "-")
            iTestArray = -1
        
        If NumberOfElements = 1 Then
        selection1.Item(1).Value.Name = InputString
        Exit Sub
        End If 'For one element no suffix is needed
        
            For Each T In TestArray
                iTestArray = iTestArray + 1
            Next T 'gets the indexlength of the user input with zero as first number
        
        If TestArray(0) = "" And Not TestArray(iTestArray) = "" Then 'minus first
            For i = 1 To NumberOfElements
                selection1.Item(i).Value.Name = selection1.Item(i).Value.Name & TestArray(1)
            Next
        
        ElseIf TestArray(iTestArray) = "" And Not TestArray(0) = "" Then 'minus last
            For i = 1 To NumberOfElements
                selection1.Item(i).Value.Name = TestArray(0) & selection1.Item(i).Value.Name
            Next
            
        Else
            For i = 1 To NumberOfElements
                selection1.Item(i).Value.Name = TestArray(0) & i
            Next
            
        End If
        
        If Err.Number <> 0 Then
            Msg = "Error # " & Str(Err.Number) & " was generated by " & Err.Source & Chr(13) & Err.Description
            MsgBox Msg, , "Error", Err.HelpFile, Err.HelpContext
        End If

End Sub

Attribute VB_Name = "TranslateAxisToAxis"
Sub CATMain()

Dim partDocument1 As PartDocument
Set partDocument1 = CATIA.ActiveDocument

Dim part1 As Part
Set part1 = partDocument1.Part

Dim bodies1 As Bodies
Set bodies1 = part1.Bodies

Dim body1 As Body
Set body1 = bodies1.Item("helperCube")

part1.InWorkObject = body1

End Sub

Attribute VB_Name = "circularSweep"
Sub CATMain()

Dim partDocument1 As PartDocument
Set partDocument1 = CATIA.ActiveDocument

Dim part1 As Part
Set part1 = partDocument1.Part

Dim hybridShapeFactory1 As HybridShapeFactory
Set hybridShapeFactory1 = part1.HybridShapeFactory

Dim hybridBodies1 As HybridBodies
Set hybridBodies1 = part1.HybridBodies

Dim hybridBody1 As HybridBody
Set hybridBody1 = hybridBodies1.Item("Geometrical Set.1")

Dim hybridShapes1 As HybridShapes
Set hybridShapes1 = hybridBody1.HybridShapes

Dim hybridShapeLinePtPt1 As HybridShapeLinePtPt
Set hybridShapeLinePtPt1 = hybridShapes1.Item("Line.1")

Dim reference1 As Reference
Set reference1 = part1.CreateReferenceFromObject(hybridShapeLinePtPt1)

Dim hybridShapeSweepCircle1 As HybridShapeSweepCircle
Set hybridShapeSweepCircle1 = hybridShapeFactory1.AddNewSweepCircle(reference1)

hybridShapeSweepCircle1.Mode = 6

hybridShapeSweepCircle1.SmoothActivity = False

hybridShapeSweepCircle1.GuideDeviationActivity = False

hybridShapeSweepCircle1.SetRadius 1, 20#

hybridShapeSweepCircle1.SetbackValue = 0.02

hybridShapeSweepCircle1.FillTwistedAreas = 1

hybridBody1.AppendHybridShape hybridShapeSweepCircle1

part1.InWorkObject = hybridShapeSweepCircle1

part1.Update

part1.Update

End Sub

Attribute VB_Name = "translate"
Sub CATMain()

Dim partDocument1 As PartDocument
Set partDocument1 = CATIA.ActiveDocument

Dim part1 As Part
Set part1 = partDocument1.Part

Dim hybridShapeFactory1 As HybridShapeFactory
Set hybridShapeFactory1 = part1.HybridShapeFactory

Dim axisSystems1 As AxisSystems
Set axisSystems1 = part1.AxisSystems

Dim axisSystem1 As AxisSystem
Set axisSystem1 = axisSystems1.Item("Absolute Axis System")

Dim reference1 As Reference
Set reference1 = part1.CreateReferenceFromBRepName("FEdge:(Edge:(Face:(Brp:(AxisSystem.1;3);None:();Cf11:());Face:(Brp:(AxisSystem.1;2);None:();Cf11:());None:(Limits1:();Limits2:());Cf11:());WithPermanentBody;WithoutBuildError;WithInitialFeatureSupport;MFBRepVersion_CXR15)", axisSystem1)

Dim hybridShapeDirection1 As HybridShapeDirection
Set hybridShapeDirection1 = hybridShapeFactory1.AddNewDirection(reference1)

Dim hybridShapeTranslate1 As HybridShapeTranslate
Set hybridShapeTranslate1 = hybridShapeFactory1.AddNewEmptyTranslate()

Dim bodies1 As Bodies
Set bodies1 = part1.Bodies

Dim body1 As Body
Set body1 = bodies1.Item("helperCube")

Dim reference2 As Reference
Set reference2 = part1.CreateReferenceFromObject(body1)

hybridShapeTranslate1.ElemToTranslate = reference2

hybridShapeTranslate1.VectorType = 0

hybridShapeTranslate1.Direction = hybridShapeDirection1

hybridShapeTranslate1.DistanceValue = 100#

hybridShapeTranslate1.VolumeResult = True

Dim hybridBodies1 As HybridBodies
Set hybridBodies1 = part1.HybridBodies

Dim hybridBody1 As HybridBody
Set hybridBody1 = hybridBodies1.Item("hybridBodyStream")

hybridBody1.AppendHybridShape hybridShapeTranslate1

part1.InWorkObject = hybridShapeTranslate1

part1.Update

Dim selection1 As Selection
Set selection1 = partDocument1.Selection

Dim visPropertySet1 As VisPropertySet
Set visPropertySet1 = selection1.VisProperties

Set hybridBodies1 = hybridBody1.Parent

Dim bSTR1 As String
bSTR1 = hybridBody1.Name

selection1.Add hybridBody1

Set visPropertySet1 = visPropertySet1.Parent

Dim bSTR2 As String
bSTR2 = visPropertySet1.Name

Dim bSTR3 As String
bSTR3 = visPropertySet1.Name

visPropertySet1.SetShow 0

selection1.Clear

End Sub
